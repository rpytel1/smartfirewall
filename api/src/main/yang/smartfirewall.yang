module smartfirewall {
    yang-version 1;
    namespace "urn:opendaylight:params:xml:ns:yang:smartfirewall";
    prefix "smartfirewall";

    revision "2015-01-05" {
        description "Initial revision of smartfirewall model";
    }

    import ietf-packet-fields {
         prefix packet-fields;
         revision-date 2016-02-18;
    }

    container access-list {
        description
          "The access-list container contains a list of access-list-entry";
        list access-list-entry {
          key "rule-name";
          description
            "Access List entry";
            container matches {
               description
                  "Definitions for match criteria";
               uses packet-fields:acl-ipv4-header-fields;
            }
           leaf rule-name {
               type string;
               description
                  "A unique name to identify this rule.";
           }
           leaf node-id {
                type string;
           }
           leaf port {
                type uint32;
           }
           leaf protocol {
                type string;
           }
       }
    }
}
